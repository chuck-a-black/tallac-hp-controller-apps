module NetUserApp {

    yang-version 1;

    //NOTE: The namespace should really have the app name in it (module name). However
    //due to maven archetype issues, we were not able to dynamically add it here.
    //If copying this project you should modify the namespace.
    namespace "brocade:netuser";

    prefix netuser;

    import ietf-inet-types { prefix "inet"; revision-date 2010-09-24; }

    organization "Brocade Communication System";

    contact
      "Sample Person <someone@com.acme.sdn.training>";

    description
      "Defines a sample yang file to illustrate containers";

    revision "2015-01-15" {
      description
        "A sample yang model describing a list of tasks. Each task maintains a operational run count, which is increased
        when the runTask RPC is invoked.";
    }

    container netuser {
    
      description
        "Top-level container for all application database objects.";
        
      list netuser-entry {
      
        key "ip-addr";
        
        leaf ip-addr {
          type inet:ipv4-address;
          description "identifier of single server.";
        }
      }
      
    }
    
    container task-container {
      description
        "Top-level container for all data. In this case the top level container only contains a list of objects (tasks).";

      list task {
        //A yang "list" is really a map and thus each entry in the "list" requires a key. In this case we
        //identify the leaf value "task-id" as the sole key of the task.
        key "task-id";

        leaf task-id {
          type string;
          description "The unique identifier of single list of tasks.";
        }

        leaf name {
          type string;
          description "The display name of the task";
        }

        leaf runCount {
          type int32;
          description "The number of times the given task has been run via the runTask RPC.";
          config false;
        }
      }
    }

    rpc runTask {
     description "Runs a given task if it exists.";
     input {
         leaf task-id {
           type string;
           description "The identifier of the task to run.";
         }
     }
    }

}
