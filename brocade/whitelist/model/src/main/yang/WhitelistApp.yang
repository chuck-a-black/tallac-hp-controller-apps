module WhitelistApp {

    yang-version 1;

    //NOTE: The namespace should really have the app name in it (module name). However
    //due to maven archetype issues, we were not able to dynamically add it here.
    //If copying this project you should modify the namespace.
    
    namespace "brocade:whitelist";

    prefix whitelist;

    import ietf-inet-types { prefix "inet"; revision-date 2010-09-24; }

    organization "Brocade Communication System";

    contact
      "Sample Person <someone@com.acme.sdn.training>";

    description
      "Defines a sample yang file to illustrate containers";

    revision "2015-01-15" {
      description
        "A definition of a whitelist, which is a list of entries to be used for setting access rights between devices."; 
    }

     container whitelist {
     
      description
        "Top-level container for all whitelist objects.";
        
      list whitelist-entry {
      
        key "ip-addr";
        leaf ip-addr {
          type inet:ipv4-address;
          description "ipv4 address of an allowed destination";
        }
      
      } 

    }
}
